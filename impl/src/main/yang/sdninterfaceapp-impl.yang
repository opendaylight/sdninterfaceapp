module sdninterfaceapp-impl {
    yang-version 1;
    namespace "urn:opendaylight:params:xml:ns:yang:sdninterfaceapp:impl";
    prefix "sdninterfaceapp-impl";

    import config { prefix config; revision-date 2013-04-05; }
    import opendaylight-md-sal-binding { prefix md-sal-binding; revision-date 2013-10-28;}

    description
        "Service definition for sdninterfaceapp project";

    revision "2015-10-06" {
        description
            "Initial revision";
    }

    identity sdninterfaceapp {
        base config:module-type;
        config:java-name-prefix sdninterfaceapp;
    }

    augment "/config:modules/config:module/config:configuration" {
        case sdninterfaceapp {
            when "/config:modules/config:module/config:type = 'sdninterfaceapp'";

            container broker {
                uses config:service-ref {
                    refine type {
                        mandatory false;
                        config:required-identity md-sal-binding:binding-broker-osgi-registry;
                    }
                }
            }

            container data-broker {
                uses config:service-ref {
                    refine type {
                        mandatory true;
                        config:required-identity md-sal-binding:binding-async-data-broker;
                    }
                }
            }

            container rpc-registry {
                uses config:service-ref {
                    refine type {
                       mandatory true;
                       config:required-identity md-sal-binding:binding-rpc-registry;
                    }
                }
            }
        }
    }
}
