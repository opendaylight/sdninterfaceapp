module sdniwrapper{
    yang-version 1;
    namespace "urn:opendaylight:params:xml:ns:yang:sdninterfaceapp:sdniwrapper";
    prefix "sdniwrapper";

    import config { prefix config; revision-date 2013-04-05; }
    import opendaylight-md-sal-binding { prefix md-sal-binding; revision-date 2013-10-28;}

    description
        "Service definition for sdninterfaceapp wrapper project";

    revision "2015-10-07" {
        description
            "Initial revision";
    }

    identity sdniwrapper {
        base config:module-type;
        config:java-name-prefix sdniwrapper;
    }

    augment "/config:modules/config:module/config:configuration" {
        case sdniwrapper {
            when "/config:modules/config:module/config:type = 'sdniwrapper'";

            container broker {
                uses config:service-ref {
                    refine type {
                        mandatory false;
                        config:required-identity md-sal-binding:binding-broker-osgi-registry;
                    }
                }
            }
           container notification-service {
               uses config:service-ref {
                   refine type {
                       mandatory true;
                       config:required-identity md-sal-binding:binding-notification-service;
                   }
               }
           } 

            container rpc-registry {
                uses config:service-ref {
                    refine type {
                       mandatory true;
                       config:required-identity md-sal-binding:binding-rpc-registry;
                    }
                }
            }

        }




    }
}
